string Message = ";This menu set was created by the Georgia Tech RoboJackets to better assist in their use of the EagleCAD software. More information about each option on the RoboJackets wiki under \"Eagle Menus\".";

status("Help");
dlgMessageBox(Message);
