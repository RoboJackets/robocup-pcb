#usage "<b>Export a SCH/BRD to IMAGE</b><p>"
       "Usage: RUN exp2image monochrome resolution image type layer <i>[layer layer]</i>"
       "<p><nobr>"
       "Tip: Assign a funktion key with<br>"
       "<tt>ASSIGN Shift+Ctrl+Alt+I 'run exp2image monochrome 150 .tif 1 17 18 20;';</tt><br>"
       "or<br>"
       "<tt>ASSIGN Shift+Ctrl+Alt+I 'run exp2image color 150 .bmp 91 92 94 95 96;';</tt>"
       "<p></nobr>"
       "<author>Author: support@cadsoft.de</author>"
       
string file_name;

string brd_suffix;
int    ratsnest = 1;       // start Ratsnest befor export image

int    sheetprint_from;
int    sheetprint_to;
int    lastsheet = 0;
string actualsheet;
int    sheetprint = 0;     // 0 = All, 1 = From To, 2 = Actual

string exp_Layers;
string sec_usedlayer[];
int    absolutUsedLayer = 0;

int    lVisible[];
int    useLayer[];
string lNames[] = { " " };

int    Resolution = 2400; // DPI
string monochrome = "";

string filetype[] = { ".bmp", // Windows-Bitmap-Datei
                      ".png", // Portable-Network-Graphics-Datei
                      ".pbm", // Portable-Bitmap-Datei
                      ".pgm", // Portable-Grayscale-Bitmap-Datei
                      ".ppm", // Portable-Pixelmap-Datei
                      ".xbm", // X-Bitmap-Datei
                      ".xpm", // X-Pixmap-Datei
                      ".tif"  // Tiff-Datei
                    };

int    select_type = 1;

string cmd = "";
int    Result = 0;
string s;

string help = usage;


// *** functions ***
void commandPrint(string name_suffix) {
  string h;
  sprintf(h, "EXPORT IMAGE '%s%s%s' %s %d;\n", file_name, name_suffix, filetype[select_type], monochrome, Resolution);
  cmd += h;
  return;
}


// main
if (argv[0]) {
    brd_suffix = "-" + argv[0];

int an = 0;
do {
  if (argv[1+an]) {
    exp_Layers += " " + argv[1+an];
    an++;
  }
  else break;
} while (an);

if (schematic) {
  schematic(S) {
    file_name = filesetext(S.name, "");
    if (sheet) sheet(SH) sprintf(actualsheet, "%d", SH.number);
    S.sheets(SH) {
      lastsheet = SH.number;
    }
    S.layers(L) {
      lNames[L.number] = L.name;
      lVisible[L.number] = L.visible;
      useLayer[L.number] = L.used;
    }
  }
  sheetprint_to = lastsheet;
}

else if (board) {
  board(B) {
    file_name = filesetext(B.name, "");
    B.layers(L) {
      lNames[L.number] = L.name;
      lVisible[L.number] = L.visible;
      useLayer[L.number] = L.used;
    }
  }
}

else if (package || symbol || deviceset) {
  library(LBR) {
    if (package) package(P) file_name = P.name;
    else if(symbol) symbol(SYM) file_name = SYM.name;
    else if (deviceset) deviceset(DEV) file_name = DEV.name;
    LBR.layers(L) {
      lNames[L.number] = L.name;
      lVisible[L.number] = L.visible;
      useLayer[L.number] = L.used;
    }
  }
}

else {
  dlgMessageBox("Start this ULP in a SCH, BRD, DEV, PAC or SYM:", "OK");
  exit(-1);
}

string layer[] ;
int n = 0;
int ln = strsplit(layer, exp_Layers, ' ');
if(board || package) {                      // 2008-06-23
  cmd += "SET DISPLAY_MODE REAL;\n";
  if (ratsnest) cmd += "RATSNEST;\n";
  cmd += "DISPLAY NONE ";

  for (int x = 0; x < ln; x++) {
    int num = strtod(layer[x]);
    if (num < 90 || num > 100) {
      if (useLayer[num]) {
        sprintf(s, " %3s", layer[x]);
        cmd += s;
        n++;
      }
    }
  }
  cmd += ";\n";
  if (board) commandPrint(brd_suffix);
  else if (package) commandPrint("-PAC");
}

if(schematic || deviceset || symbol) {
  cmd += "DISPLAY NONE ";
  for (int x = 0; x < ln; x++) {
    int num = strtod(layer[x]);
    if (useLayer[num]) {
      if (num >= 90) {
        sprintf(s, " %3s", layer[x]);
        cmd += s;
        n++;
      }
    }
  }
  cmd += ";\n";
  string sh;
  string shn;
  if (schematic) {  // 2008-06-23
    switch (sheetprint) {
      case 0 : schematic(S) {
               S.sheets(SH) {
                 sprintf(sh, "EDIT '.s%d';\n", SH.number);
                 cmd += sh;
                 sprintf(shn, "_s%d", SH.number);
                 commandPrint(shn);
               }
             }
             break;

      case 1 : for (int prn = sheetprint_from; prn <= sheetprint_to; prn++) {
               sprintf(sh, "EDIT '.s%d';\n", prn);
               cmd += sh;
               sprintf(shn, "_s%d", prn);
               commandPrint(shn);
             }
             break;

      case 2 : sprintf(sh, "EDIT '.s%s';\n", actualsheet);
             cmd += sh;
             sprintf(shn, "_s%s", actualsheet);
             commandPrint(shn);
             break;
    }
  }
  else if (deviceset) commandPrint("-DEV");
  else if (symbol) commandPrint("-SYM");

}

cmd += "DISPLAY ";
if(board || package) {
  for(int l = 1; l < 90; l++) {
    if (useLayer[l]) {
      if (lVisible[l]) {
        sprintf(s, " %d", l);
        cmd += s;
      }
      else {
        sprintf(s, " -%d", l);
        cmd += s;
      }
    }
  }
  for(l = 100; l < 256; l++) {
    if (useLayer[l]) {
      if (lVisible[l]) {
        sprintf(s, " %d", l);
        cmd += s;
      }
      else {
        sprintf(s, " -%d", l);
        cmd += s;
      }
    }
  }
  cmd += ";\n";
}

if(schematic || deviceset || symbol) { // 2008-06-23
  for(int l = 91; l < 256; l++) {
    if (useLayer[l]) {
      if (lVisible[l]) {
        sprintf(s, " %d", l);
        cmd += s;
      }
      else {
        sprintf(s, " -%d", l);
        cmd += s;
      }
    }
  }
  cmd += ";\n";
  if(schematic) {      // 2008-06-23 alf@cadsoft.de
    sprintf(s, "EDIT '.s%s';\n", actualsheet);
    cmd += s;
  }
}

exit (cmd);
